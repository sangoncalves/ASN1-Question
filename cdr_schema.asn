CDR DEFINITIONS AUTOMATIC TAGS ::= 

BEGIN
AccessPointNameNI ::= IA5String (SIZE(1..100))

AccessPointNameOI ::= IA5String (SIZE(1..37))

AdditionalExceptionReports ::= ENUMERATED { notAllowed (0), allowed (1) }

IPBinV4Address ::= OCTET STRING (SIZE(4))

IPBinV6Address ::= OCTET STRING (SIZE(16))

maxAddressLength INTEGER ::= 20

AddressString ::= OCTET STRING (SIZE (1..maxAddressLength))

AFChargingIdentifier ::= OCTET STRING (SIZE(1..63))

BCDDirectoryNumber ::= OCTET STRING

BSID ::= OCTET STRING (SIZE(1..12))

CallDuration ::= INTEGER

CallReferenceNumber ::= OCTET STRING (SIZE (1..8))

CellID ::= OCTET STRING (SIZE(2))

ChargingCharacteristics ::= OCTET STRING(SIZE(2))

ChargingID ::= INTEGER (0..4294967295)

ChargingRuleBaseName ::= IA5String (SIZE(1..36))

CPCIoTEPSOptimisationIndicator ::= BOOLEAN

CSGAccessMode ::= ENUMERATED { closedMode (0), hybridMode (1) }

CSGId ::= OCTET STRING (SIZE(4..8))

CTEID::= OCTET STRING (SIZE(4))

DataVolumeGPRS ::= INTEGER

DataVolumeMBMS ::= INTEGER

DiameterIdentity ::= OCTET STRING (SIZE(1..127))

DynamicAddressFlag ::= BOOLEAN

maxExt-GeographicalInformation INTEGER ::= 91

Ext-GeographicalInformation ::= OCTET STRING (SIZE (1..maxExt-GeographicalInformation))

ESN ::= OCTET STRING (SIZE(1..15))

FailureHandlingContinue ::= BOOLEAN

FFDAppendIndicator ::= BOOLEAN

FreeFormatData ::= OCTET STRING (SIZE(1..160))

HardwareID::= CHOICE { eSN [1] ESN, mEID [2] MEID }

HSGWChange ::= BOOLEAN

TBCD-STRING ::= OCTET STRING 
-- TBCD-STRING ::= IA5String
-- TBCD-STRING ::= IA5String (SIZE(1..36))
-- TBCD-STRING ::= INTEGER (1..64)
-- TBCD-STRING ::= NumericString (SIZE(9))
-- TBCD-STRING ::= UTF8String
-- TBCD-STRING ::= BMPString
-- TBCD-STRING ::= BIT STRING

IMSI ::= TBCD-STRING (SIZE(3..8))
-- IMSI ::= TBCD-STRING (SIZE (1..8))
-- IMSI ::= NumericString (SIZE (12))
-- IMSI ::= PrintableString (SIZE (1..20))
-- IMSI ::= OCTET STRING (SIZE(9))
-- IMSI ::= IA5String (SIZE(7..15))
-- IMSI ::= INTEGER (1..64)
-- IMSI ::= REAL (1..64)

IMEI ::= TBCD-STRING (SIZE (1..8)) 

PDPAddressPrefixLength ::= INTEGER (1..64)

IPPort ::= OCTET STRING (SIZE(2))

LCSCause ::= OCTET STRING (SIZE(1))

LCSLocationAreaCode ::= OCTET STRING (SIZE(9))

LCS-Priority ::= OCTET STRING (SIZE (1))

LCSQoSInfo ::= OCTET STRING (SIZE(4))

LevelOfCAMELService ::= BIT STRING { basic (0), callDurationSupervision (1), onlineCharging (2) }

LocationAreaAndCell ::= SEQUENCE { locationAreaCode [0] LCSLocationAreaCode OPTIONAL }

LocationAreaCode ::= OCTET STRING (SIZE(2))

RequiredMBMSBearerCapabilities ::= OCTET STRING (SIZE (3..14))

MBMSSessionIdentity ::= OCTET STRING (SIZE (1))

TMGI ::= OCTET STRING (SIZE(6))

MBMSServiceArea::= OCTET STRING(SIZE (1..513))

ManagementExtension ::=INTEGER

ManagementExtensions ::= INTEGER

MEID ::= OCTET STRING (SIZE(1..14))

MessageReference ::= OCTET STRING(SIZE(1..2))

MSNetworkCapability ::= OCTET STRING (SIZE(1..8))

MSTimeZone ::= OCTET STRING (SIZE (2))

NetworkInitiatedPDPContext ::= BOOLEAN

NodeID ::= IA5String (SIZE(1..20))

IPBinV6AddressWithPrefixLength ::= SEQUENCE {iPBinV6Address [1] IPBinV6Address OPTIONAL, pDPAddressPrefixLength [2] PDPAddressPrefixLength OPTIONAL }

IPBinV6AddressWithOrWithoutPrefixLength ::= CHOICE { iPBinV6Address [1] IPBinV6Address,iPBinV6AddressWithPrefix [4] IPBinV6AddressWithPrefixLength }

IPBinaryAddress ::= CHOICE { iPBinV4Address [0] IPBinV4Address, iPBinV6Address IPBinV6AddressWithOrWithoutPrefixLength }

RecordSeqNumber ::= OCTET STRING(SIZE(3))

ResultCode ::= INTEGER

RoutingAreaCode ::= OCTET STRING (SIZE(1..2))

SecondaryRATType ::= INTEGER { nR (0)}

-- RATType ::= INTEGER
-- {
--     reserved          (0),
--     uTRAN             (1),
--     gERAN             (2),
--     wLAN              (3),
--     gAN               (4),
--     hSPAEvolution     (5),
--     eUTRAN            (6),
--     virtual           (7),
--     eUTRAN-NB-IoT     (8),
--     nG-RAN            (51),
--     iEEE802-16e       (101),
--     eHRPDfor3GPP2     (102),
--     hRPD3GPP2         (103),
--     onexRTTfor3GPP2   (104),
--     uMBfor3GPP2       (105)
-- }

Served3GPP2MEID ::= OCTET STRING(SIZE(1..14))

ServiceConditionChange ::= OCTET STRING (SIZE(4..5))

ServiceKey ::= OCTET STRING(SIZE(1..5))

RncID ::= SEQUENCE { plmnId [0] PlmnId OPTIONAL, rncId [1] INTEGER (0..4095) OPTIONAL }

SGSNChange ::= BOOLEAN

SGWChange ::= BOOLEAN

SUBNET ::= OCTET STRING (SIZE(1..37))

SubscriptionIDData ::= OCTET STRING (SIZE(1..64))

TimeStamp ::= OCTET STRING (SIZE(9))
-- TimeStamp ::= NumericString (SIZE (9))
--TimeStamp ::= UTCTime
--TimeStamp ::= GeneralizedTime
--TimeStamp ::= GeneralString
-- TimeStamp ::= DATE-TIME



UmtsQosInformation ::= OCTET STRING(SIZE(4..17))

UmtsUserLocationInformation ::= OCTET STRING (SIZE(8))

UNIPDUCPOnlyFlag::= BOOLEAN

UserLocationInformation ::= OCTET STRING (SIZE(6..34))

IPTextRepresentedAddress ::= CHOICE { iPTextV4Address [2] IA5String (SIZE(7..15)), iPTextV6Address [3] IA5String (SIZE(15..45)) }

--IPAddress ::= CHOICE { iPBinaryAddress IPBinaryAddress, iPTextRepresentedAddress IPTextRepresentedAddress }

IPAddress ::= CHOICE { iPBinV4Address [0] IPBinV4Address, iPBinV6Address [1] IPBinV6Address, iPTextV4Address [2] IA5String (SIZE(7..15)), iPTextV6Address [3] IA5String (SIZE(15..45)) }

GSNAddress ::= IPAddress

AddressSequenceNumberList ::= SEQUENCE { gsnAddress [0] GSNAddress OPTIONAL, sequenceNumberList [1] SEQUENCE OF INTEGER OPTIONAL }

AFRecordInformation ::= SEQUENCE { aFChargingIdentifier [1] AFChargingIdentifier OPTIONAL }

APNRateControl ::= SEQUENCE { aPNRateControlUplink [0] APNRateControlParameters OPTIONAL, aPNRateControlDownlink [1] APNRateControlParameters OPTIONAL }

APNRateControlParameters ::= SEQUENCE { additionalExceptionReports [0] AdditionalExceptionReports OPTIONAL, rateControlTimeUnit [1] RateControlTimeUnit OPTIONAL, rateControlMaxRate [2] INTEGER OPTIONAL }

APNSelectionMode::= ENUMERATED { mSorNetworkProvidedSubscriptionVerified (0), mSProvidedSubscriptionNotVerified (1), networkProvidedSubscriptionNotVerified (2) }

CallingNumber ::= BCDDirectoryNumber

CAMELAccessPointNameNI ::= AccessPointNameNI

CAMELAccessPointNameOI ::= AccessPointNameOI

PacketNum ::= INTEGER (0..4294967295)

CAMELInformationMM ::= SET { sCFAddress [1] SCFAddress OPTIONAL, serviceKey [2] ServiceKey OPTIONAL, defaultTransactionHandling [3] DefaultGPRS-Handling OPTIONAL, numberOfDPEncountered [4] NumberOfDPEncountered OPTIONAL, levelOfCAMELService [5] LevelOfCAMELService OPTIONAL, freeFormatData [6] FreeFormatData OPTIONAL, fFDAppendIndicator [7] FFDAppendIndicator OPTIONAL }

CAMELInformationPDP ::= SET { sCFAddress [1] SCFAddress OPTIONAL, serviceKey [2] ServiceKey OPTIONAL, defaultTransactionHandling [3] DefaultGPRS-Handling OPTIONAL, cAMELAccessPointNameNI [4] CAMELAccessPointNameNI OPTIONAL, cAMELAccessPointNameOI [5] CAMELAccessPointNameOI OPTIONAL, numberOfDPEncountered [6] NumberOfDPEncountered OPTIONAL, levelOfCAMELService [7] LevelOfCAMELService OPTIONAL, freeFormatData [8] FreeFormatData OPTIONAL, fFDAppendIndicator [9] FFDAppendIndicator OPTIONAL }

CAMELInformationSMS ::= SET { sCFAddress [1] SCFAddress OPTIONAL, serviceKey [2] ServiceKey OPTIONAL, defaultSMSHandling [3] DefaultSMS-Handling OPTIONAL, cAMELCallingPartyNumber [4] CallingNumber OPTIONAL, cAMELDestinationSubscriberNumber [5] SmsTpDestinationNumber OPTIONAL, cAMELSMSCAddress [6] AddressString OPTIONAL, freeFormatData [7] FreeFormatData OPTIONAL, sMSReferenceNumber [8] CallReferenceNumber OPTIONAL }

CauseForRecClosing ::= INTEGER { normalRelease (0), abnormalRelease (4), cAMELInitCallRelease (5), volumeLimit (16), timeLimit (17), servingNodeChange (18), maxChangeCond (19), managementIntervention (20), intraSGSNIntersystemChange (21), rATChange (22), mSTimeZoneChange (23), sGSNPLMNIDChange (24), mOExceptionDataCounterReceipt (27), unauthorizedRequestingNetwork (52), unauthorizedLCSClient (53), positionMethodFailure (54), unknownOrUnreachableLCSClient (58), listofDownstreamNodeChange (59), pcrfProvideNewQoS (99) }

ChangeCondition ::= ENUMERATED { qoSChange (0), tariffTime (1), recordClosure (2), failureHandlingContinueOngoing (3), failureHandlingRetryandTerminateOngoing (4), failureHandlingTerminateOngoing (5), cGI-SAICHange (6), rAIChange (7), dT-Establishment (8), dT-Removal (9), eCGIChange (10), tAIChange (11), userLocationChange (12),
userPlaneToUEChange (18), servingPLMNRateControlChange (19) }

QoSReliability ::= ENUMERATED { subscribedReliabilityClass (0), acknowledgedGTP (1), unackGTPAcknowLLC (2), unackGTPLLCAcknowRLC (3), unackGTPLLCRLC (4), unacknowUnprotectedData (5), reserved6 (6), reserved7 (7) }

QoSDelay ::= ENUMERATED { subscribedDelayClass (0), delayClass1 (1), delayClass2 (2), delayClass3 (3), delayClass4 (4), reserved5 (5), reserved6 (6), reserved7 (7) }

QoSPrecedence ::= ENUMERATED { subscribedPrecedence (0), highPriority (1), normalPriority (2), lowPriority (3), reserved4 (4), reserved5 (5), reserved6 (6), reserved7 (7) }

QoSPeakThroughput ::= ENUMERATED { subscribedPeakThroughput (0), upTo1000octetPs (1), upTo2000octetPs (2), upTo4000octetPs (3), upTo8000octetPs (4), upTo16000octetPs (5), upTo32000octetPs (6), upTo64000octetPs (7), upTo128000octetPs (8), upTo256000octetPs (9), reserved10 (10), reserved11 (11), reserved12 (12), reserved13 (13), reserved14 (14), reserved15 (15) }

QoSMeanThroughput ::= ENUMERATED { subscribedMeanThroughput (0), mean100octetPh (1), mean200octetPh (2), mean500octetPh (3), mean1000octetPh (4), mean2000octetPh (5), mean5000octetPh (6), mean10000octetPh (7), mean20000octetPh (8), mean50000octetPh (9), mean100000octetPh (10), mean200000octetPh (11), mean500000octetPh (12), mean1000000octetPh (13), mean2000000octetPh (14), mean5000000octetPh (15), mean10000000octetPh (16), mean20000000octetPh (17), mean50000000octetPh (18), reserved19 (19), reserved20 (20), reserved21 (21),reserved22 (22), reserved23 (23), reserved24 (24), reserved25 (25), reserved26 (26), reserved27 (27), reserved28 (28), reserved29 (29), reserved30 (30), bestEffort (31) }

GSMQoSInformation ::=SEQUENCE { reliability [0] QoSReliability OPTIONAL, delay [1] QoSDelay OPTIONAL, precedence [2] QoSPrecedence OPTIONAL, peakThroughput [3] QoSPeakThroughput OPTIONAL, meanThroughput [4] QoSMeanThroughput OPTIONAL }

EPCQoSInformation ::= SEQUENCE {qCI [1] INTEGER OPTIONAL, maxRequestedBandwithUL [2] INTEGER OPTIONAL, maxRequestedBandwithDL [3] INTEGER OPTIONAL, guaranteedBitrateUL [4] INTEGER OPTIONAL, guaranteedBitrateDL [5] INTEGER OPTIONAL, aRP [6] INTEGER OPTIONAL, aPNAggregateMaxBitrateUL [7] INTEGER OPTIONAL, aPNAggregateMaxBitrateDL [8] INTEGER OPTIONAL, extendedMaxRequestedBWUL [9] INTEGER OPTIONAL, extendedMaxRequestedBWDL [10] INTEGER OPTIONAL, extendedGBRUL [11] INTEGER OPTIONAL, extendedGBRDL [12] INTEGER OPTIONAL, extendedAPNAMBRUL [13] INTEGER OPTIONAL, extendedAPNAMBRDL [14] INTEGER OPTIONAL }

QoSInformation ::= CHOICE {gsmQosInformation [0] GSMQoSInformation, umtsQosInformation [1] UmtsQosInformation, ePCQoSInformation [2] EPCQoSInformation }

ChangeOfMBMSCondition ::= SEQUENCE { qosRequested [1] QoSInformation OPTIONAL, qosNegotiated [2] QoSInformation OPTIONAL, dataVolumeMBMSUplink [3] DataVolumeMBMS OPTIONAL, dataVolumeMBMSDownlink [4] DataVolumeMBMS OPTIONAL, changeCondition [5] ChangeCondition OPTIONAL, changeTime [6] TimeStamp OPTIONAL, tariffLevel [7] INTEGER OPTIONAL }

ChangeLocation ::= SEQUENCE { locationAreaCode [0] LocationAreaCode OPTIONAL, routingAreaCode [1] RoutingAreaCode OPTIONAL, cellID [2] CellID OPTIONAL, changeTime [3] TimeStamp OPTIONAL }

ChChSelectionMode ::= ENUMERATED { servingNodeSupplied (0), subscriptionSpecific (1),aPNSpecific (2),homeDefault (3),roamingDefault (4), visitingDefault (5)}

ConsolidationResult ::= ENUMERATED {normal (0), notNormal (1), forInterSGSNConSolidation (2), reachLimit (3), onlyOneCDRGenerated (4)}

UWANUserLocationInfo::= SEQUENCE { uELocalIPAddress [0] IPAddress OPTIONAL, uDPSourcePort [1] IPPort OPTIONAL }

ServingNodeType ::= ENUMERATED { sGSN (0), pMIPSGW (1), gTPSGW (2), ePDG (3), hSGW (4), mME (5), tWAN (6), aMF (7), sMF (8),iSMF (9), ePCF (100) }

ServingPLMNRateControl ::= SEQUENCE { sPLMNDLRateControlValue [0] INTEGER, sPLMNULRateControlValue [1] INTEGER }

SGiPtPTunnellingMethod ::= ENUMERATED { uDPIPbased (0), others (1) }

UserLocationInformationFor5G::= OCTET STRING (SIZE(9..17))

RatingGroupId ::= INTEGER

ServiceChargeType ::= ENUMERATED { volume (0), time (1), volumeAndTime (2), event (3), timeAndEvent (4), volumeAndEvent (5), volumeAndTimeAndEvent (6) }

ThreeGPP2UserLocationInformation ::= OCTET STRING(SIZE(1..37))

ChangeOfCharCondition ::= SEQUENCE { qosRequested [1] QoSInformation OPTIONAL, qosNegotiated [2] QoSInformation OPTIONAL, dataVolumeGPRSUplink [3] DataVolumeGPRS OPTIONAL, dataVolumeGPRSDownlink [4] DataVolumeGPRS OPTIONAL, changeCondition [5] ChangeCondition OPTIONAL, changeTime [6] TimeStamp OPTIONAL, tariffLevel [7] INTEGER OPTIONAL, ePCUserLocationInformation [8] UserLocationInformation OPTIONAL, ePCQoSInformation [9] EPCQoSInformation OPTIONAL, uWANUserLocationInformation [17] UWANUserLocationInfo OPTIONAL, cPCIoTEPSOptimisationIndicator [19] CPCIoTEPSOptimisationIndicator OPTIONAL, servingPLMNRateControl [20] ServingPLMNRateControl OPTIONAL, userLocationInformationFor5G [101] UserLocationInformationFor5G OPTIONAL}

ChangeOfCharConditionForMEC ::= SEQUENCE { dataVolumeGPRSUplink [3] DataVolumeGPRS OPTIONAL, dataVolumeGPRSDownlink [4] DataVolumeGPRS OPTIONAL, changeCondition [5] ChangeCondition OPTIONAL, changeTime [6] TimeStamp OPTIONAL, tariffLevel [7] INTEGER OPTIONAL, ePCUserLocationInformation [8] UserLocationInformation OPTIONAL, ePCQoSInformation [9] EPCQoSInformation OPTIONAL, cPCIoTEPSOptimisationIndicator [19] CPCIoTEPSOptimisationIndicator OPTIONAL, servingPLMNRateControl [20] ServingPLMNRateControl OPTIONAL}

ServiceConditionChangeEx ::= BIT STRING { qoSChange (0), sGSNChange (1), sGSNPLMNIDChange (2), tariffTimeSwitch (3), pDPContextRelease (4), rATChange (5), serviceIdledOut (6), qCTExpiry (7),configurationChange (8), serviceStop (9), dCCATimeThresholdReached (10), dCCAVolumeThresholdReached (11), dCCAServiceSpecificUnitThresholdReached (12), dCCATimeExhausted (13), dCCAVolumeExhausted (14), dCCAValidityTimeout (15), returnRequested (16),dCCAReauthorisationRequest (17), dCCAContinueOngoingSession (18), dCCARetryAndTerminateOngoingSession (19), dCCATerminateOngoingSession (20), cGI-SAIChange (21), rAIChange (22), dCCAServiceSpecificUnitExhausted (23), recordClosure (24), timeLimit (25), volumeLimit (26), serviceSpecificUnitLimit (27), envelopeClosure (28), eCGIChange (29), tAIChange (30), userLocationChange (31), userCSGInformationChange (32), presenceInPRAChange (33), accessChangeOfSDF (34), indirectServiceConditionChange (35), servingPLMNRateControlChange (36), aPNRateControlChange (37) }

ChangeOfServiceCondition ::= SEQUENCE { ratingGroup [1] RatingGroupId OPTIONAL, chargingRuleBaseName [2] ChargingRuleBaseName OPTIONAL, resultCode [3] ResultCode OPTIONAL, localSequenceNumber [4] INTEGER OPTIONAL, timeOfFirstUsage [5] TimeStamp OPTIONAL, timeOfLastUsage [6] TimeStamp OPTIONAL, timeUsage [7] CallDuration OPTIONAL, serviceConditionChange [8] ServiceConditionChange OPTIONAL, qoSInformationNeg [9] QoSInformation OPTIONAL, servingNodeAddress [10] GSNAddress OPTIONAL, datavolumeFBCUplink [12] INTEGER OPTIONAL, datavolumeFBCDownlink [13] INTEGER OPTIONAL, timeOfReport [14] TimeStamp OPTIONAL, failureHandlingContinue [16]FailureHandlingContinue OPTIONAL, serviceIdentifier [17] INTEGER OPTIONAL, aFRecordInformation [19] SEQUENCE OF AFRecordInformation OPTIONAL, userLocationInformation [20] UserLocationInformation OPTIONAL, eventCounter [24] INTEGER OPTIONAL, l7UpVolume [25] INTEGER OPTIONAL, l7DownVolume [26] INTEGER OPTIONAL, attemptCounter [27] INTEGER OPTIONAL, serviceChargeType [28] ServiceChargeType OPTIONAL, threeGPP2UserLocationInformation [29] ThreeGPP2UserLocationInformation OPTIONAL, sponsorIdentity [30] OCTET STRING (SIZE(1..128)) OPTIONAL, applicationServiceProviderIdentity [31] OCTET STRING (SIZE(1..128)) OPTIONAL, uWANUserLocationInformation [32] UWANUserLocationInfo OPTIONAL, servingPLMNRateControl [35] ServingPLMNRateControl OPTIONAL, aPNRateControl [36] APNRateControl OPTIONAL, url [100] IA5String(SIZE(1..64)) OPTIONAL, serviceConditionChangeEx [101] ServiceConditionChangeEx OPTIONAL, uplinkPacketNum [102] PacketNum OPTIONAL, downlinkPacketNum [103] PacketNum OPTIONAL,userLocationInformationFor5G [104] UserLocationInformationFor5G OPTIONAL}

ContentChargeInformation ::= SEQUENCE { serviceCode [0] INTEGER OPTIONAL, upVolume [1] INTEGER OPTIONAL, downVolume [2] INTEGER OPTIONAL, qosNegotiated [3] QoSInformation OPTIONAL, usageDuration [4] INTEGER OPTIONAL, ratingGroup [5] RatingGroupId OPTIONAL, rusultCode [6] ResultCode OPTIONAL, timeOfFirstUsage [7] TimeStamp OPTIONAL, timeOfLastUsage [8] TimeStamp OPTIONAL, serviceConditionChange [9] ServiceConditionChange OPTIONAL, timeOfReport [10] TimeStamp OPTIONAL, failureHandlingContinue [11] FailureHandlingContinue OPTIONAL, eventCounter [12] INTEGER OPTIONAL, l7UpVolume [13] INTEGER OPTIONAL, l7DownVolume [14] INTEGER OPTIONAL, attemptCounter [15] INTEGER OPTIONAL, serviceChargeType [16] ServiceChargeType OPTIONAL, userLocationInformation [17] UmtsUserLocationInformation OPTIONAL, ePCQoSInformation [18] EPCQoSInformation OPTIONAL,ePCUserLocationInformation [19] UserLocationInformation OPTIONAL, url [100] IA5String(SIZE(1..64)) OPTIONAL }

ContentExtensions::= SEQUENCE { extensionType [0] ExtensionType OPTIONAL, extensionInformation [1] ExtensionInformation OPTIONAL }

CTC-ChangeOfCharCondition ::= SEQUENCE { dataVolumeGPRSUplink [3] DataVolumeGPRS OPTIONAL, dataVolumeGPRSDownlink [4] DataVolumeGPRS OPTIONAL, changeCondition [5] ChangeCondition OPTIONAL, changeTime [6] TimeStamp OPTIONAL, ePCUserLocationInformation [8] UserLocationInformation OPTIONAL, ePCQoSInformation [9] EPCQoSInformation OPTIONAL }

DefaultGPRS-Handling ::= ENUMERATED { continueTransaction (0), releaseTransaction (1) }

DefaultSMS-Handling ::= ENUMERATED { continueTransaction (0) , releaseTransaction (1) }

DeferredLocationEventType ::= BIT STRING { msAvailable (0) , enteringIntoArea (1), leavingFromArea (2), beingInsideArea (3) , periodicLDR (4) } (SIZE (1..16))

Diagnostics ::= CHOICE { gsm0408Cause [0] INTEGER,gsm0902MapErrorValue[1] INTEGER, ccittQ767Cause [2] INTEGER,networkSpecificCause [3] ManagementExtensions,manufacturerSpecificCause [4] ManagementExtensions,positionMethodFailureCause [5] PositionMethodFailure-Diagnostic,unauthorizedLCSClientCause [6] UnauthorizedLCSClient-Diagnostic}

ETSIAddress ::= AddressString

ExtensionInformation ::= CHOICE { contentCharge [0] SEQUENCE OF ContentChargeInformation }

ExtensionType ::= ENUMERATED { contentCharge (1) }


ISDN-AddressString ::= AddressString

LCSClientExternalID ::= SEQUENCE { externalAddress [0] ISDN-AddressString OPTIONAL }

LCSClientInternalID ::= ENUMERATED { broadcastService (0), o-andM-HPLMN (1), o-andM-VPLMN (2), anonymousLocation (3),targetMSsubscribedService (4) }

LCSClientIdentity ::= SEQUENCE { lcsClientExternalID [0] LCSClientExternalID OPTIONAL, lcsClientDialedByMS [1] AddressString OPTIONAL, lcsClientInternalID [2] LCSClientInternalID OPTIONAL }

LCSClientType ::= ENUMERATED { emergencyServices (0), valueAddedServices (1), plmnOperatorServices (2), lawfulInterceptServices (3) }


LocationEstimateType ::= ENUMERATED { currentLocation (0), currentOrLastKnownLocation (1), initialLocation (2), activateDeferredLocation (3), cancelDeferredLocation (4), notificationVerificationOnly (5) }

LocationMethod::= ENUMERATED { msBasedEOTD (0), msAssistedEOTD (1), assistedGPS (2), msBasedOTDOA (3), assistedGANSS (4), assistedGPSandGANSS (5) }

LocationType ::= SEQUENCE { locationEstimateType [0] LocationEstimateType OPTIONAL, deferredLocationEventType [1] DeferredLocationEventType OPTIONAL }

MBMSInformation ::= SET { tMGI [1] TMGI OPTIONAL, mBMSSessionIdentity [2] MBMSSessionIdentity OPTIONAL, mBMSServiceType [3] MBMSServiceType OPTIONAL, mBMSUserServiceType [4] MBMSUserServiceType OPTIONAL,mBMS2G3GIndicator [5] MBMS2G3GIndicator OPTIONAL,fileRepairSupported [6] BOOLEAN OPTIONAL,rAI [7] RoutingAreaCode OPTIONAL,mBMSServiceArea [8] MBMSServiceArea OPTIONAL, requiredMBMSBearerCaps [9] RequiredMBMSBearerCapabilities OPTIONAL, mBMSGWAddress [10] GSNAddress OPTIONAL, cNIPMulticastDistribution [11] CNIPMulticastDistribution OPTIONAL, mBMSAccessIndicator [12]MBMSAccessIndicator OPTIONAL}

MBMS2G3GIndicator ::= ENUMERATED { is2G (0),is3G (1),is2G-AND-3G (2)}

MBMSServiceType ::= ENUMERATED { mULTICAST (0), bROADCAST (1) }

MBMSUserServiceType ::= ENUMERATED { dOWNLOAD (0), sTREAMING (1) }

CNIPMulticastDistribution ::= ENUMERATED { nO-IP-MULTICAST (0), iP-MULTICAST (1) }

MBMSAccessIndicator ::= ENUMERATED { uTRAN (0), eUTRAN (1), uTRAN-AND-EUTRAN (2) }

MOExceptionDataCounter ::= SEQUENCE { counterValue [0] INTEGER, counterTimestamp [1] TimeStamp }

MSISDN ::= ISDN-AddressString

NotificationToMSUser ::= ENUMERATED { notifyLocationAllowed (0), notifyAndVerify-LocationAllowedIfNoResponse (1), notifyAndVerify-LocationNotAllowedIfNoResponse (2), locationNotAllowed (3) }

PDNConnectionID ::= INTEGER

NumberOfDPEncountered ::= INTEGER

PDPType ::= OCTET STRING (SIZE(2))

PlmnId::= OCTET STRING (SIZE(3))

PositioningData ::= OCTET STRING (SIZE (1..33))

PDPPDNTypeExtension ::= INTEGER { ipv4 (0), ppp (1), ipv6 (2), ipv4v6 (3), nonIP (4) }

RAIdentity ::= OCTET STRING (SIZE (6))

PDPAddress ::= CHOICE { iPAddress [0] IPAddress, eTSIAddress [1] ETSIAddress }

RateControlTimeUnit ::= INTEGER { unrestricted (0), minute (1), hour (2), day (3), week (4) }

PositionMethodFailure-Diagnostic ::= ENUMERATED { congestion (0), insufficientResources (1), insufficientMeasurementData (2), inconsistentMeasurementData (3), locationProcedureNotCompleted (4), locationProcedureNotSupportedByTargetMS (5), qoSNotAttainable (6), positionMethodNotAvailableInNetwork (7), positionMethodNotAvailableInLocationArea (8) }

PSFurnishChargingInformation ::= SEQUENCE { pSFreeFormatData [1] FreeFormatData OPTIONAL, pSFFDAppendIndicator [2] FFDAppendIndicator OPTIONAL }

RANSecondaryRATUsageReport ::= SEQUENCE { dataVolumeUplink [1] DataVolumeGPRS, dataVolumeDownlink [2] DataVolumeGPRS, rANStartTime [3] TimeStamp, rANEndTime [4] TimeStamp, secondaryRATType [5] SecondaryRATType }

RATType ::= INTEGER { reserved (0), uTRAN (1), gERAN (2), wLAN (3), gAN (4), hSPAEvolution (5), eUTRAN (6), virtual (7), eUTRAN-NB-IoT (8), nG-RAN (51), iEEE802-16e (101), eHRPDfor3GPP2 (102), hRPD3GPP2 (103), onexRTTfor3GPP2 (104), uMBfor3GPP2 (105) }

RecordingEntity ::= AddressString

SCFAddress ::= ISDN-AddressString

SCSASAddress ::= SET{ sCSAddress [1] IPAddress, sCSRealm [2] DiameterIdentity }

SMSResult ::= Diagnostics

SmsTpDestinationNumber ::= BCDDirectoryNumber

SubscriptionID ::= SET { subscriptionIDType [1] SubscriptionIDType OPTIONAL, subscriptionIDData [2] SubscriptionIDData OPTIONAL }

SubscriptionIDType ::= ENUMERATED { eND-USER-E164 (0), eND-USER-IMSI (1), eND-USER-SIP-URI (2), eND-USER-NAI (3), eND-USER-PRIVATE (4) }

SystemType ::= ENUMERATED { unknown (0), iuUTRAN (1), gERAN (2) }

TWANUserLocationInfo ::= SEQUENCE { sSID [0] OCTET STRING (SIZE(1..32)) OPTIONAL, bSSID [1] OCTET STRING (SIZE(6)) OPTIONAL }

UnauthorizedLCSClient-Diagnostic ::= ENUMERATED { noAdditionalInformation (0), clientNotInMSPrivacyExceptionList (1), callToClientNotSetup (2), privacyOverrideNotApplicable (3), disallowedByLocalRegulatoryRequirements (4), unauthorizedPrivacyClass (5), unauthorizedCallSessionUnrelatedExternalClient (6), unauthorizedCallSessionRelatedExternalClient (7) }

UserCSGInformation ::= SEQUENCE { cSGId [0] CSGId OPTIONAL, cSGAccessMode [1] CSGAccessMode OPTIONAL, cSGMembershipIndication [2] NULL OPTIONAL }

CallEventRecordType ::= INTEGER { sgsnPDPRecord (18), ggsnPDPRecord (19), sgsnMMRecord (20), sgsnSMORecord (21), sgsnSMTRecord (22), sgsnMtLCSRecord (26), sgsnMoLCSRecord (27), sgsnNiLCSRecord (28), sgsnMBMSRecord (45), ggsnMBMSRecord (46), sGWRecord (84), pGWRecord (85), gwMBMSRecord (86), ePDGRecord (96), wLANRecord (201), hSGWRecord (200) }

SGSNPDPRecord ::= SET {recordType [0] CallEventRecordType, networkInitiation [1] NetworkInitiatedPDPContext OPTIONAL, servedIMSI [3] IMSI OPTIONAL, servedIMEI [4] IMEI OPTIONAL, sgsnAddressList [5] SEQUENCE OF GSNAddress OPTIONAL, msNetworkCapability [6] MSNetworkCapability OPTIONAL, routingArea [7] RoutingAreaCode OPTIONAL, locationAreaCode [8] LocationAreaCode OPTIONAL, cellIdentifier [9] CellID OPTIONAL, chargingID [10] ChargingID OPTIONAL, ggsnAddressUsed [11] GSNAddress OPTIONAL, accessPointNameNI [12] AccessPointNameNI OPTIONAL, pdpType [13] PDPType OPTIONAL, servedPDPAddress [14] PDPAddress OPTIONAL, listOfTrafficVolumes [15] SEQUENCE OF ChangeOfCharCondition OPTIONAL, recordOpeningTime [16] TimeStamp OPTIONAL, duration [17] CallDuration OPTIONAL, sgsnChange [18] SGSNChange OPTIONAL, causeForRecClosing [19] CauseForRecClosing OPTIONAL, diagnostics [20] Diagnostics OPTIONAL, listOfRecordSequenceNumber [21] SEQUENCE OF AddressSequenceNumberList OPTIONAL, nodeID [22] NodeID OPTIONAL, recordExtensions [23] ManagementExtensions OPTIONAL, localSequenceNumber [24] RecordSeqNumber, apnSelectionMode [25] APNSelectionMode OPTIONAL, accessPointNameOI [26] AccessPointNameOI OPTIONAL, servedMSISDN [27] MSISDN OPTIONAL, chargingCharacteristics [28] ChargingCharacteristics OPTIONAL, systemType [29] SystemType OPTIONAL, cAMELInformationPDP [30] CAMELInformationPDP OPTIONAL, rNCUnsentDownlinkVolume [31] DataVolumeGPRS OPTIONAL, consolidationResult [32] ConsolidationResult OPTIONAL, chgLocalSeqNoList [33] SEQUENCE OF AddressSequenceNumberList OPTIONAL, chChSelectionMode [34] ChChSelectionMode OPTIONAL, dynamicAddressFlag [35] DynamicAddressFlag OPTIONAL, cellPLMNID [36] PlmnId OPTIONAL, servedPDPPDNAddressExt [37] PDPAddress OPTIONAL }

CallEventRecord ::= CHOICE {sgsnPDPRecord [20] SGSNPDPRecord, ggsnPDPRecord [21] GGSNPDPRecord, sgsnMMRecord [22] SGSNMMRecord, sgsnSMORecord [23] SGSNSMORecord, sgsnSMTRecord [24] SGSNSMTRecord,sgsnMtLCSRecord [25] SGSNMTLCSRecord, sgsnMoLCSRecord [26] SGSNMOLCSRecord, sgsnNiLCSRecord SGSNNILCSRecord, sgsnMBMSRecord [29] SGSNMBMSRecord, ggsnMBMSRecord [30] GGSNMBMSRecord, sGWRecord [78] SGWRecord, pGWRecord [79] PGWRecord, wLANRecord [80] WLANRecord, gwMBMSRecord [86] GWMBMSRecord, ePDGRecord [96] EPDGRecord, hSGWRecord [200] HSGWRecord }

GGSNPDPRecord ::= SET {recordType [0] CallEventRecordType, networkInitiation [1] NetworkInitiatedPDPContext OPTIONAL, servedIMSI [3] IMSI OPTIONAL, ggsnAddress [4] GSNAddress OPTIONAL, chargingID [5] ChargingID OPTIONAL,  sgsnAddress [6] SEQUENCE OF GSNAddress OPTIONAL, accessPointNameNI [7] AccessPointNameNI OPTIONAL, pdpType [8] PDPType OPTIONAL, servedPDPAddress [9] PDPAddress OPTIONAL, dynamicAddressFlag [11] DynamicAddressFlag OPTIONAL,  listOfTrafficVolumes [12] SEQUENCE OF ChangeOfCharCondition OPTIONAL, recordOpeningTime [13] TimeStamp OPTIONAL, duration [14] CallDuration OPTIONAL, causeForRecClosing [15] CauseForRecClosing OPTIONAL, diagnostics [16] Diagnostics OPTIONAL,  listOfRecordSequenceNumber [17] SEQUENCE OF AddressSequenceNumberList OPTIONAL, nodeID [18] NodeID OPTIONAL, recordExtensions [19] ContentExtensions OPTIONAL, localSequenceNumber [20] RecordSeqNumber, apnSelectionMode [21] APNSelectionMode OPTIONAL, servedMSISDN [22] MSISDN OPTIONAL, chargingCharacteristics [23] ChargingCharacteristics OPTIONAL, localSeqNoList [26] AddressSequenceNumberList OPTIONAL, sgsnPLMNIdentifier [27] PlmnId OPTIONAL, chChSelectionMode [28] ChChSelectionMode OPTIONAL, rATType [29] RATType OPTIONAL, consolidationResult [30] ConsolidationResult OPTIONAL, iMSsignalingContext [32] NULL OPTIONAL, externalChargingID [33] OCTET STRING OPTIONAL, userLocationInformation [34] UmtsUserLocationInformation OPTIONAL,  servedIMEISV [35] IMEI OPTIONAL, mSTimeZone [36] MSTimeZone OPTIONAL, url [37] IA5String (SIZE(1..64)) OPTIONAL, iMSIunauthenticatedFlag [38] NULL OPTIONAL, roamingIndicator [101] INTEGER OPTIONAL, diameterSessionID [102] IA5String (SIZE(1..128)) OPTIONAL, servedPDPPDNAddressExt [103] PDPAddress OPTIONAL, pSFurnishChargingInformation [104] PSFurnishChargingInformation OPTIONAL, ePCUserLocationInformation [105] UserLocationInformation OPTIONAL, ePCQoSInformation [106] EPCQoSInformation OPTIONAL }

SGSNMMRecord ::= SET { recordType [0] CallEventRecordType,  servedIMSI [1] IMSI OPTIONAL, servedIMEI [2] IMEI OPTIONAL, sgsnAddress [3] GSNAddress OPTIONAL, msNetworkCapability [4] MSNetworkCapability OPTIONAL, routingArea [5] RoutingAreaCode OPTIONAL,  locationAreaCode [6] LocationAreaCode OPTIONAL, cellIdentifier [7] CellID OPTIONAL, changeLocation [8] SEQUENCE OF ChangeLocation OPTIONAL, recordOpeningTime [9] TimeStamp OPTIONAL, duration [10] CallDuration OPTIONAL,  sgsnChange [11] SGSNChange OPTIONAL, causeForRecClosing [12] CauseForRecClosing OPTIONAL, diagnostics [13] Diagnostics OPTIONAL, recordSequenceNumber [14] INTEGER OPTIONAL, nodeID [15] NodeID OPTIONAL,  recordExtensions [16] ManagementExtensions OPTIONAL, localSequenceNumber [17] RecordSeqNumber, servedMSISDN [18] MSISDN OPTIONAL, chargingCharacteristics [19] ChargingCharacteristics OPTIONAL, cAMELInformationMM [20] CAMELInformationMM OPTIONAL, systemType [21] SystemType OPTIONAL, chChSelectionMode [22] ChChSelectionMode OPTIONAL,cellPLMNID [23] PlmnId OPTIONAL }


SGSNSMORecord ::= SET { recordType [0] CallEventRecordType, servedIMSI [1] IMSI OPTIONAL, servedIMEI [2] IMEI OPTIONAL, servedMSISDN [3] MSISDN OPTIONAL, msNetworkCapability [4] MSNetworkCapability OPTIONAL, serviceCentre [5] AddressString OPTIONAL, recordingEntity [6] RecordingEntity OPTIONAL, locationArea [7] LocationAreaCode OPTIONAL, routingArea [8] RoutingAreaCode OPTIONAL, cellIdentifier [9] CellID OPTIONAL, messageReference [10] MessageReference OPTIONAL, originationTime [11] TimeStamp OPTIONAL, smsResult [12] SMSResult OPTIONAL, recordExtensions [13] ManagementExtensions OPTIONAL, nodeID [14] NodeID OPTIONAL, localSequenceNumber [15] RecordSeqNumber, chargingCharacteristics [16] ChargingCharacteristics OPTIONAL, systemType [17] SystemType OPTIONAL, destinationNumber [18] BCDDirectoryNumber OPTIONAL, cAMELInformationSMS [19] CAMELInformationSMS OPTIONAL, chChSelectionMode [20] ChChSelectionMode OPTIONAL, cellPLMNID [101] PlmnId OPTIONAL }

SGSNSMTRecord ::= SET { recordType [0] CallEventRecordType, servedIMSI [1] IMSI OPTIONAL, servedIMEI [2] IMEI OPTIONAL, servedMSISDN [3] MSISDN OPTIONAL, msNetworkCapability [4] MSNetworkCapability OPTIONAL, serviceCentre [5] AddressString OPTIONAL, recordingEntity [6] RecordingEntity OPTIONAL, locationArea [7] LocationAreaCode OPTIONAL, routingArea [8] RoutingAreaCode OPTIONAL, cellIdentifier [9] CellID OPTIONAL, originationTime [10] TimeStamp OPTIONAL, smsResult [11] SMSResult OPTIONAL, recordExtensions [12] ManagementExtensions OPTIONAL, nodeID [13] NodeID OPTIONAL, localSequenceNumber [14] RecordSeqNumber, chargingCharacteristics [15] ChargingCharacteristics OPTIONAL, systemType [16] SystemType OPTIONAL, cAMELInformationSMS [17] CAMELInformationSMS OPTIONAL, chChSelectionMode [18] ChChSelectionMode OPTIONAL, originationNumber [19] BCDDirectoryNumber OPTIONAL, cellPLMNID [101] PlmnId OPTIONAL }

SGSNMOLCSRecord ::= SET { recordType [0] CallEventRecordType, recordingEntity [1]  RecordingEntity OPTIONAL, lcsClientType [2] LCSClientType OPTIONAL, lcsClientIdentity [3] LCSClientIdentity OPTIONAL, servedIMSI [4] IMSI OPTIONAL, servedMSISDN [5] MSISDN OPTIONAL, sgsnAddress [6] GSNAddress OPTIONAL, locationMethod [7] LocationMethod OPTIONAL, lcsQos [8] LCSQoSInfo OPTIONAL, lcsPriority [9] LCS-Priority OPTIONAL, mlcNumber [10] ISDN-AddressString OPTIONAL,eventTimeStamp [11] TimeStamp OPTIONAL, measurementDuration [12] CallDuration OPTIONAL, location [13] LocationAreaAndCell OPTIONAL, routingArea [14] RoutingAreaCode OPTIONAL, locationEstimate [15] Ext-GeographicalInformation OPTIONAL, positioningData [16] PositioningData OPTIONAL, lcsCause [17] LCSCause OPTIONAL, diagnostics [18] Diagnostics OPTIONAL, nodeID [19] NodeID OPTIONAL, localSequenceNumber [20] RecordSeqNumber, chargingCharacteristics [21] ChargingCharacteristics OPTIONAL, chChSelectionMode [22] ChChSelectionMode OPTIONAL, rATType [23] RATType OPTIONAL, recordExtensions [24] ManagementExtensions OPTIONAL, causeForRecClosing [25] CauseForRecClosing OPTIONAL }

SGSNMTLCSRecord ::= SET { recordType [0] CallEventRecordType, recordingEntity [1] RecordingEntity OPTIONAL, lcsClientType [2] LCSClientType OPTIONAL, lcsClientIdentity [3] LCSClientIdentity OPTIONAL, servedIMSI [4] IMSI OPTIONAL, servedMSISDN [5] MSISDN OPTIONAL, sgsnAddress [6] GSNAddress OPTIONAL, locationType [7] LocationType OPTIONAL, lcsQos [8] LCSQoSInfo OPTIONAL, lcsPriority [9] LCS-Priority OPTIONAL, mlcNumber [10] ISDN-AddressString OPTIONAL, eventTimeStamp [11] TimeStamp OPTIONAL, measurementDuration [12] CallDuration OPTIONAL, notificationToMSUser [13] NotificationToMSUser OPTIONAL, privacyOverride [14] NULL OPTIONAL, location [15] LocationAreaAndCell OPTIONAL, routingArea [16] RoutingAreaCode OPTIONAL, locationEstimate [17] Ext-GeographicalInformation OPTIONAL, positioningData [18] PositioningData OPTIONAL, lcsCause [19] LCSCause OPTIONAL, diagnostics [20] Diagnostics OPTIONAL, nodeID [21] NodeID OPTIONAL, localSequenceNumber [22] RecordSeqNumber, chargingCharacteristics [23] ChargingCharacteristics OPTIONAL, chChSelectionMode [24] ChChSelectionMode OPTIONAL, rATType [25] RATType OPTIONAL, recordExtensions [26] ManagementExtensions OPTIONAL, causeForRecClosing [27] CauseForRecClosing OPTIONAL }

SGSNNILCSRecord ::= SET { recordType [0] CallEventRecordType, recordingEntity [1] RecordingEntity OPTIONAL, lcsClientType [2] LCSClientType OPTIONAL, lcsClientIdentity [3] LCSClientIdentity OPTIONAL, servedIMSI [4] IMSI OPTIONAL, servedMSISDN [5] MSISDN OPTIONAL, sgsnAddress [6] GSNAddress OPTIONAL, servedIMEI [7] IMEI OPTIONAL, lcsQos [8] LCSQoSInfo OPTIONAL, lcsPriority [9] LCS-Priority OPTIONAL, mlcNumber [10] ISDN-AddressString OPTIONAL, eventTimeStamp [11] TimeStamp OPTIONAL, measurementDuration [12] CallDuration OPTIONAL, location [13] LocationAreaAndCell OPTIONAL, routingArea [14] RoutingAreaCode OPTIONAL, locationEstimate [15] Ext-GeographicalInformation OPTIONAL,positioningData [16] PositioningData OPTIONAL, lcsCause [17] LCSCause OPTIONAL, diagnostics [18] Diagnostics OPTIONAL, nodeID [19] NodeID OPTIONAL, localSequenceNumber [20] RecordSeqNumber, chargingCharacteristics [21] ChargingCharacteristics OPTIONAL, chChSelectionMode [22] ChChSelectionMode OPTIONAL, rATType [23] RATType OPTIONAL, recordExtensions [24] ManagementExtensions OPTIONAL, causeForRecClosing [25] CauseForRecClosing OPTIONAL }

SGSNMBMSRecord ::= SET { recordType [0] CallEventRecordType, ggsnAddress [1] GSNAddress OPTIONAL, chargingID [2] ChargingID OPTIONAL, listofRAs [3] SEQUENCE OF RAIdentity OPTIONAL, accessPointNameNI [4] AccessPointNameNI OPTIONAL, servedPDPAddress [5] PDPAddress OPTIONAL, listOfTrafficVolumes [6] SEQUENCE OF ChangeOfMBMSCondition OPTIONAL, recordOpeningTime [7] TimeStamp OPTIONAL, duration [8] CallDuration OPTIONAL, causeForRecClosing [9] CauseForRecClosing OPTIONAL, diagnostics [10] Diagnostics OPTIONAL, recordSequenceNumber [11] INTEGER OPTIONAL, nodeID [12] NodeID OPTIONAL, recordExtensions [13] ManagementExtensions OPTIONAL, localSequenceNumber [14] RecordSeqNumber, sgsnPLMNIdentifier [15] PlmnId OPTIONAL, numberofReceivingUE [16] INTEGER OPTIONAL, mbmsInformation [17] MBMSInformation OPTIONAL }

GGSNMBMSRecord ::= SET { recordType [0] CallEventRecordType, ggsnAddress [1] GSNAddress OPTIONAL, chargingID [2] ChargingID OPTIONAL, listofDownstreamNodes [3] SEQUENCE OF GSNAddress OPTIONAL, accessPointNameNI [4] AccessPointNameNI OPTIONAL, servedPDPAddress [5] PDPAddress OPTIONAL, listOfTrafficVolumes [6] SEQUENCE OF ChangeOfMBMSCondition OPTIONAL, recordOpeningTime [7] TimeStamp OPTIONAL, duration [8] CallDuration OPTIONAL, causeForRecClosing [9] CauseForRecClosing OPTIONAL, diagnostics [10] Diagnostics OPTIONAL, recordSequenceNumber [11] INTEGER OPTIONAL, nodeID [12] NodeID OPTIONAL, recordExtensions [13] ManagementExtensions OPTIONAL, localSequenceNumber [14] RecordSeqNumber, mbmsInformation [15] MBMSInformation OPTIONAL }

GWMBMSRecord ::= SET { recordType [0] CallEventRecordType, mbmsGWAddress [1] GSNAddress OPTIONAL, chargingID [2] ChargingID OPTIONAL, listofDownstreamNodes [3] SEQUENCE OF GSNAddress OPTIONAL, accessPointNameNI [4] AccessPointNameNI OPTIONAL, pdpPDNType [5] PDPType OPTIONAL, servedPDPPDNAddress [6] PDPAddress OPTIONAL, listOfTrafficVolumes [7] SEQUENCE OF ChangeOfMBMSCondition OPTIONAL, recordOpeningTime [8] TimeStamp OPTIONAL, duration [9] CallDuration OPTIONAL, causeForRecClosing [10] CauseForRecClosing OPTIONAL,diagnostics [11] Diagnostics OPTIONAL, recordSequenceNumber [12] INTEGER OPTIONAL, nodeID [13] NodeID OPTIONAL, recordExtensions [14] ManagementExtensions OPTIONAL, localSequenceNumber [15] RecordSeqNumber, mbmsInformation [16] MBMSInformation OPTIONAL, commonTeid [17] CTEID OPTIONAL, iPMulticastSourceAddress [18] PDPAddress OPTIONAL }

SGWRecord ::= SET { recordType [0] CallEventRecordType, servedIMSI [3] IMSI OPTIONAL, s-GWAddress [4] SEQUENCE OF GSNAddress OPTIONAL, chargingID [5] ChargingID OPTIONAL, servingNodeAddress [6] SEQUENCE OF GSNAddress OPTIONAL, accessPointNameNI [7] AccessPointNameNI OPTIONAL, pdpPDNType [8] PDPType OPTIONAL, servedPDPPDNAddress [9] PDPAddress OPTIONAL, dynamicAddressFlag [11] DynamicAddressFlag OPTIONAL, listOfTrafficVolumes [12] SEQUENCE OF ChangeOfCharCondition OPTIONAL, recordOpeningTime [13] TimeStamp OPTIONAL, duration [14] CallDuration OPTIONAL, causeForRecClosing [15] CauseForRecClosing OPTIONAL, diagnostics [16] Diagnostics OPTIONAL, listOfRecordSequenceNumber [17] SEQUENCE OF AddressSequenceNumberList OPTIONAL, nodeID [18] NodeID OPTIONAL, recordExtensions [19] ManagementExtensions OPTIONAL, localSequenceNumber [20] RecordSeqNumber, apnSelectionMode [21] APNSelectionMode OPTIONAL, servedMSISDN [22] MSISDN OPTIONAL, chargingCharacteristics [23] ChargingCharacteristics OPTIONAL, chChSelectionMode [24] ChChSelectionMode OPTIONAL, iMSsignalingContext [25] NULL OPTIONAL, servingNodePLMNIdentifier [27] PlmnId OPTIONAL, servedIMEISV [29] IMEI OPTIONAL, rATType [30] RATType OPTIONAL, mSTimeZone [31] MSTimeZone OPTIONAL, userLocationInformation [32] UserLocationInformation OPTIONAL, sGWChange [34] SGWChange OPTIONAL, servingNodeType [35] SEQUENCE OF ServingNodeType OPTIONAL, p-GWAddressUsed [36] GSNAddress OPTIONAL, p-GWPLMNIdentifier [37] PlmnId OPTIONAL, startTime [38] TimeStamp OPTIONAL, stopTime [39] TimeStamp OPTIONAL, pDNConnectionID [40] ChargingID OPTIONAL, chgLocalSeqNoList [41] SEQUENCE OF AddressSequenceNumberList OPTIONAL, consolidationResult [42] ConsolidationResult OPTIONAL, iMSIunauthenticatedFlag [43] NULL OPTIONAL, lowPriorityIndicator [44] NULL OPTIONAL, dynamicAddressFlagExt [47] DynamicAddressFlag OPTIONAL, cPCIoTEPSOptimisationIndicator [59] CPCIoTEPSOptimisationIndicator OPTIONAL, uNIPDUCPOnlyFlag [60] UNIPDUCPOnlyFlag OPTIONAL, servingPLMNRateControl [61] ServingPLMNRateControl OPTIONAL, pDPPDNTypeExtension [62] PDPPDNTypeExtension OPTIONAL, mOExceptionDataCounter [63] MOExceptionDataCounter OPTIONAL, listOfRANSecondaryRATUsageReports [64] SEQUENCE OF RANSecondaryRATUsageReport OPTIONAL, servedPDPPDNAddressExt [100] PDPAddress OPTIONAL, userCSGInformation [101] UserCSGInformation OPTIONAL, listOfTrafficVolumesForMEC [201] SEQUENCE OF ChangeOfCharConditionForMEC OPTIONAL }

PGWRecord ::= SET { recordType [0] CallEventRecordType,servedIMSI [3] IMSI OPTIONAL, p-GWAddress [4] GSNAddress OPTIONAL, chargingID [5] ChargingID OPTIONAL, servingNodeAddress [6] SEQUENCE OF GSNAddress OPTIONAL, accessPointNameNI [7] AccessPointNameNI OPTIONAL, pdpPDNType [8] PDPType OPTIONAL, servedPDPPDNAddress [9] PDPAddress OPTIONAL, dynamicAddressFlag [11] DynamicAddressFlag OPTIONAL, listOfTrafficVolumes [12] SEQUENCE OF ChangeOfCharCondition OPTIONAL, recordOpeningTime [13] TimeStamp OPTIONAL, duration [14] CallDuration OPTIONAL, causeForRecClosing [15] CauseForRecClosing OPTIONAL, diagnostics [16] Diagnostics OPTIONAL, listOfRecordSequenceNumber [17] SEQUENCE OF AddressSequenceNumberList OPTIONAL, nodeID [18] NodeID OPTIONAL, recordExtensions [19] ManagementExtensions OPTIONAL, localSequenceNumber [20] RecordSeqNumber, apnSelectionMode [21] APNSelectionMode OPTIONAL, servedMSISDN [22] MSISDN OPTIONAL, chargingCharacteristics [23] ChargingCharacteristics OPTIONAL, chChSelectionMode [24] ChChSelectionMode OPTIONAL, iMSsignalingContext [25] NULL OPTIONAL, externalChargingID [26] OCTET STRING OPTIONAL, servingNodePLMNIdentifier [27] PlmnId OPTIONAL, servedIMEISV [29] IMEI OPTIONAL, rATType [30] RATType OPTIONAL, mSTimeZone [31] MSTimeZone OPTIONAL, userLocationInformation [32] UserLocationInformation OPTIONAL, listOfServiceData [34] SEQUENCE OF ChangeOfServiceCondition OPTIONAL, servingNodeType [35] SEQUENCE OF ServingNodeType OPTIONAL, servedMNNAI [36] SubscriptionID OPTIONAL, p-GWPLMNIdentifier [37] PlmnId OPTIONAL, startTime [38] TimeStamp OPTIONAL, stopTime [39] TimeStamp OPTIONAL, pDNConnectionID [41] ChargingID OPTIONAL, chgLocalSeqNoList [42] SEQUENCE OF AddressSequenceNumberList OPTIONAL, consolidationResult [43] ConsolidationResult OPTIONAL, iMSIunauthenticatedFlag [44] NULL OPTIONAL, threeGPP2UserLocationInformation [45] ThreeGPP2UserLocationInformation OPTIONAL, tWANUserLocationInformation [46] TWANUserLocationInfo OPTIONAL, dynamicAddressFlagExt [47] DynamicAddressFlag OPTIONAL, ePCQoSInformation [55] EPCQoSInformation OPTIONAL, uWANUserLocationInformation [62] UWANUserLocationInfo OPTIONAL, sGiPtPTunnellingMethod [64] SGiPtPTunnellingMethod OPTIONAL, uNIPDUCPOnlyFlag [65] UNIPDUCPOnlyFlag OPTIONAL, servingPLMNRateControl [66] ServingPLMNRateControl OPTIONAL, aPNRateControl [67] APNRateControl OPTIONAL, pDPPDNTypeExtension [68] PDPPDNTypeExtension OPTIONAL, mOExceptionDataCounter [69] MOExceptionDataCounter OPTIONAL, sCSASAddress [72] SCSASAddress OPTIONAL, listOfRANSecondaryRATUsageReports [73] SEQUENCE OF RANSecondaryRATUsageReport OPTIONAL, roamingIndicator [101] INTEGER OPTIONAL, diameterSessionID [102] IA5String (SIZE(1..128)) OPTIONAL, servedPDPPDNAddressExt [103] PDPAddress OPTIONAL, userCSGInformation [105] UserCSGInformation OPTIONAL, pSFurnishChargingInformation [106] PSFurnishChargingInformation OPTIONAL, lowPriorityIndicator [107] NULL OPTIONAL, spLocation [108] IA5String (SIZE(1..16)) OPTIONAL, userLocationInformationFor5G [109] UserLocationInformationFor5G OPTIONAL}

WLANRecord ::= SET { recordType [0] CallEventRecordType, servedIMSI [1] IMSI OPTIONAL, servedMSISDN [2] MSISDN OPTIONAL,servedIMEI [3] IMEI OPTIONAL, pDGAddress [4] GSNAddress OPTIONAL, nodeID [5] NodeID OPTIONAL, servingProxyAddress [6] GSNAddress OPTIONAL, pdpType [7] PDPType OPTIONAL, remoteIPAddress [8] PDPAddress OPTIONAL, chargingID [9] ChargingID OPTIONAL, wLanSessionID [10] INTEGER (0..4294967295) OPTIONAL, accessPointNameNI [11] AccessPointNameNI OPTIONAL, chargingCharacteristics [12] ChargingCharacteristics OPTIONAL, chChSelectionMode [13] ChChSelectionMode OPTIONAL, recordOpeningTime [14] TimeStamp OPTIONAL, duration [15] CallDuration OPTIONAL, causeForRecClosing [16] CauseForRecClosing OPTIONAL, listOfRecordSequenceNumber [17] SEQUENCE OF AddressSequenceNumberList OPTIONAL, localSequenceNumber [18] RecordSeqNumber, diagnostics [19] Diagnostics OPTIONAL, listOfTrafficVolumes [20] SEQUENCE OF ChangeOfCharCondition OPTIONAL, recordExtensions [21] ContentExtensions OPTIONAL }

HSGWRecord ::= SET { recordType [0] CallEventRecordType, servedIMSI [3] IMSI OPTIONAL, s-GWAddressUsed [4] IPAddress OPTIONAL, chargingID [5] ChargingID OPTIONAL, servingNodeAddress [6] SEQUENCE OF IPAddress OPTIONAL, accessPointNameNI [7] AccessPointNameNI OPTIONAL, pdpPDNType [8] PDPType OPTIONAL, servedPDPPDNAddress [9] PDPAddress OPTIONAL, dynamicAddressFlag [11] DynamicAddressFlag OPTIONAL, listOfTrafficVolumes [12] SEQUENCE OF CTC-ChangeOfCharCondition OPTIONAL, recordOpeningTime [13] TimeStamp OPTIONAL, duration [14] CallDuration OPTIONAL, causeForRecClosing [15] CauseForRecClosing OPTIONAL, diagnostics [16] Diagnostics OPTIONAL, recordSequenceNumber [17] INTEGER OPTIONAL, nodeID [18] NodeID OPTIONAL, recordExtensions [19] ManagementExtensions OPTIONAL, localSequenceNumber [20] RecordSeqNumber, apnSelectionMode [21] APNSelectionMode OPTIONAL, servedMSISDN [22] MSISDN OPTIONAL, chargingCharacteristics [23] ChargingCharacteristics OPTIONAL, chChSelectionMode [24] ChChSelectionMode OPTIONAL, servingNodePLMNIdentifier [27] PlmnId OPTIONAL, servedIMEISV [29] IMEI OPTIONAL, rATType [30] RATType OPTIONAL, threeGPP2UserLocationInformation [32] ThreeGPP2UserLocationInformation OPTIONAL, sGWChange [34] SGWChange OPTIONAL, servingNodeType [35] SEQUENCE OF ServingNodeType OPTIONAL, p-GWAddressUsed [36] IPAddress OPTIONAL, startTime [38] TimeStamp OPTIONAL, stopTime [39] TimeStamp OPTIONAL, served3gpp2MEID [40] Served3GPP2MEID OPTIONAL, iMSIunauthenticatedFlag [41] NULL OPTIONAL, servedPDPPDNAddressExt [43] PDPAddress OPTIONAL, dynamicAddressFlagExt [47] DynamicAddressFlag OPTIONAL, s-GWAddressUsedIPv6 [48] IPAddress OPTIONAL, servingNodeAddressIPv6 [49] SEQUENCE OF IPAddress OPTIONAL, p-GWAddressUsedIPv6 [50] IPAddress OPTIONAL }

EPDGRecord::= SET { recordType [0] CallEventRecordType,servedIMSI [3] IMSI OPTIONAL, ePDGAddressUsed [4] GSNAddress OPTIONAL, chargingID [5] ChargingID OPTIONAL, accessPointNameNI [7] AccessPointNameNI OPTIONAL, pdpPDNType [8] PDPType OPTIONAL, servedPDPPDNAddress [9] PDPAddress OPTIONAL, dynamicAddressFlag [11] DynamicAddressFlag OPTIONAL, listOfTrafficVolumes [12] SEQUENCE OF ChangeOfCharCondition OPTIONAL, recordOpeningTime [13] TimeStamp OPTIONAL, duration [14] CallDuration OPTIONAL, causeForRecClosing [15] CauseForRecClosing OPTIONAL, diagnostics [16] Diagnostics OPTIONAL, recordSequenceNumber [17] INTEGER OPTIONAL, nodeID [18] NodeID OPTIONAL, recordExtensions [19] ManagementExtensions OPTIONAL, localSequenceNumber [20] RecordSeqNumber, apnSelectionMode [21] APNSelectionMode OPTIONAL, servedMSISDN [22] MSISDN OPTIONAL, chargingCharacteristics [23] ChargingCharacteristics OPTIONAL, chChSelectionMode [24] ChChSelectionMode OPTIONAL, iMSsignalingContext [25] NULL OPTIONAL, rATType [30] RATType OPTIONAL, sGWChange [34] SGWChange OPTIONAL, p-GWAddressUsed [36] GSNAddress OPTIONAL, p-GWPLMNIdentifier [37] PlmnId OPTIONAL, startTime [38] TimeStamp OPTIONAL, stopTime [39] TimeStamp OPTIONAL, pDNConnectionChargingID [40] ChargingID OPTIONAL, servedPDPPDNAddressExt [43] PDPAddress OPTIONAL, dynamicAddressFlagExt [47] DynamicAddressFlag OPTIONAL, uWANUserLocationInformation [53] UWANUserLocationInfo OPTIONAL }

END
